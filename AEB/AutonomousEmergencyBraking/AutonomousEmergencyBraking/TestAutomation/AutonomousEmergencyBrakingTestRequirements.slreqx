# AutonomousEmergencyBrakingTestRequirements

## 1: scenario_01_AEB_Bicyclist_Longitudinal_25width (Functional)
| Test Description | Target vehicles | Requirements on Vehicle Under Test |
| --- | --- | --- |
| scenario_01_AEB_Bicyclist_Longitudinal_25width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 | Bicyclist: constant velocity of 5.55 m/s Event: The ego vehicle collides with the bicyclist that is in front of it. Before the collision, the bicyclist and ego vehicle are traveling in the same direction along the longitudinal axis. At collision time, the bicycle is 25% of the way across the width of the ego vehicle. | Travels with constant velocity: 13.89 m/s Expected behavior: Ego vehicle should brake ahead of the bicyclist to avoid collision. |

## 2: scenario_02_AEB_Bicyclist_Longitudinal_50width (Functional)
| Test Description | Target vehicles | Requirements on Vehicle Under Test |
| --- | --- | --- |
| scenario_02_AEB_Bicyclist_Longitudinal_50width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 | Bicyclist: Travels with a constant velocity of 4.17 m/s. Event: The ego vehicle collides with the bicyclist that is in front of it. Before the collision, the bicyclist and ego vehicle are traveling in the same direction along the longitudinal axis. At collision time, the bicycle is 50% of the way across the width of the ego vehicle. | Travels with constant velocity: 6.94 m/s. Expected behavior: Ego vehicle should brake ahead of the bicyclist to avoid collision. |

## 3: scenario_03_AEB_Bicyclist_Longitudinal_75width (Functional)
| Test Description | Target vehicles | Requirements on Vehicle Under Test |  |  |  |
| --- | --- | --- | --- | --- | --- |
| scenario_03_AEB_Bicyclist_Longitudinal_75width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 | Bicyclist: Travels with a constant velocity of 4.17 m/s. Event: The ego vehicle collides with the bicyclist that is in front of it. Before the collision, the bicyclist and ego vehicle are traveling in the same direction along the longitudinal axis. At collision time, the bicycle is 75% of the way across the width of the ego vehicle. | Travels with constant velocity: 6.94 m/s. Expected behavior: Ego vehicle should brake ahead of the bicyclist to avoid collision. |  |  |  |

## 4: scenario_04_AEB_CCRb_2_initialGap_12m (Functional)
| Test Description | Target vehicles | Requirements on Vehicle Under Test |
| --- | --- | --- |
| scenario_04_AEB_CCRb_2_initialGap_12m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 | Braking Vehicle: Initially travels with a constant velocity of 13.89 m/s. And then begins to decelerate at 2 m/s2. Initial gap = 12 meters. Event: A collision in which ego vehicle travels forward towards another vehicle that is travelling at constant speed and then decelerates, and the ego vehicle strikes the rear structure of the target vehicle. | Travels with constant velocity: 13.89 m/s. Expected behavior: Forward collision warning (FCW) and triggering of Autonomous Emergency Braking (AEB) which stops the ego vehicle by applying brakes to avoid collision. |

## 5: scenario_05_AEB_CCRb_2_initialGap_40m (Functional)
| Test Description | Target vehicles | Requirements on Vehicle Under Test |
| --- | --- | --- |
| scenario_05_AEB_CCRb_2_initialGap_40m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 | Braking Vehicle: Initially travels with a constant velocity of 13.89 m/s. And then begins to decelerate at 2 m/s2. Initial gap = 40 meters. Event: A collision in which ego vehicle travels forward towards another vehicle that is travelling at constant speed and then decelerates, and the ego vehicle strikes the rear structure of the target vehicle. | Travels with constant velocity: 13.89 m/s. Expected behavior: Forward collision warning (FCW) and triggering of Autonomous Emergency Braking (AEB) which stops the ego vehicle by applying brakes to avoid collision. |

## 6: scenario_06_AEB_CCRb_6_initialGap_12m (Functional)
| Test Description | Target vehicles | Requirements on Vehicle Under Test |
| --- | --- | --- |
| scenario_06_AEB_CCRb_6_initialGap_12m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 | Braking Vehicle: Initially travels with a constant velocity of 13.89 m/s. And then begins to decelerate at 6 m/s2. Initial gap = 12 meters. Event: A collision in which ego vehicle travels forward towards another vehicle that is travelling at constant speed and then decelerates, and the ego vehicle strikes the rear structure of the target vehicle. | Travels with constant velocity: 13.89 m/s. Expected behavior: Forward collision warning (FCW) and triggering of Autonomous Emergency Braking (AEB) which stops the ego vehicle by applying brakes to avoid collision. |

## 7: scenario_07_AEB_CCRb_6_initialGap_40m (Functional)
| Test Description | Target vehicles | Requirements on Vehicle Under Test |
| --- | --- | --- |
| scenario_07_AEB_CCRb_6_initialGap_40m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 | Braking Vehicle: Initially travels with a constant velocity of 13.89 m/s. And then begins to decelerate at 6 m/s2. Initial gap = 40 meters. Event: A collision in which ego vehicle travels forward towards another vehicle that is travelling at constant speed and then decelerates, and the ego vehicle strikes the rear structure of the target vehicle. | Travels with constant velocity: 13.89 m/s. Expected behavior: Forward collision warning (FCW) and triggering of Autonomous Emergency Braking (AEB) which stops the ego vehicle by applying brakes to avoid collision. |

## 8: scenario_08_AEB_CCRm_50overlap (Functional)
| Test Description | Target vehicles | Requirements on Vehicle Under Test |
| --- | --- | --- |
| scenario_08_AEB_CCRm_50overlap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 | Moving Vehicle: Travels with a constant velocity of 5.5 m/s. Event: A collision in which the ego vehicle rear-ends a moving vehicle. At collision time, the ego vehicle overlaps with 50% of the width of the moving vehicle. | Travels with constant velocity: 8.33 m/s. Expected behavior: Forward collision warning (FCW) and triggering of Autonomous Emergency Braking (AEB) which stops the ego vehicle by applying brakes to avoid collision. |

## 9: scenario_09_AEB_CCRm_-50overlap (Functional)
| Test Description | Target vehicles | Requirements on Vehicle Under Test |
| --- | --- | --- |
| scenario_09_AEB_CCRm_-50overlap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 | Moving Vehicle: Travels with a constant velocity of 5.5 m/s. Event: A collision in which the ego vehicle rear-ends a moving vehicle. At collision time, the ego vehicle overlaps with -50% of the width of the moving vehicle. When the ego vehicle is to the left of the other vehicle, the percent overlap is negative. | Travels with constant velocity: 8.33 m/s. Expected behavior: Forward collision warning (FCW) and triggering of Autonomous Emergency Braking (AEB) which stops the ego vehicle by applying brakes to avoid collision. |

## 10: scenario_10_AEB_CCRm_75overlap (Functional)
| Test Description | Target vehicles | Requirements on Vehicle Under Test |
| --- | --- | --- |
| scenario_10_AEB_CCRm_75overlap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 | Moving Vehicle: Travels with a constant velocity of 5.5 m/s. Event: A collision in which the ego vehicle rear-ends a moving vehicle. At collision time, the ego vehicle overlaps with 75% of the width of the moving vehicle. | Travels with constant velocity: 8.33 m/s. Expected behavior: Forward collision warning (FCW) and triggering of Autonomous Emergency Braking (AEB) which stops the ego vehicle by applying brakes to avoid collision. |

## 11: scenario_11_AEB_CCRm_-75overlap (Functional)
| Test Description | Target vehicles | Requirements on Vehicle Under Test |
| --- | --- | --- |
| scenario_11_AEB_CCRm_-75overlap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 | Moving Vehicle: Travels with a constant velocity of 5.5 m/s. Event: A collision in which the ego vehicle rear-ends a moving vehicle. At collision time, the ego vehicle overlaps with -75% of the width of the moving vehicle. When the ego vehicle is to the left of the other vehicle, the percent overlap is negative. | Travels with constant velocity: 8.33 m/s. Expected behavior: Forward collision warning (FCW) and triggering of Autonomous Emergency Braking (AEB) which stops the ego vehicle by applying brakes to avoid collision. |

## 12: scenario_12_AEB_CCRm_100overlap (Functional)
| Test Description | Target vehicles | Requirements on Vehicle Under Test |
| --- | --- | --- |
| scenario_12_AEB_CCRm_100overlap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 | Moving Vehicle: Travels with a constant velocity of 5.5 m/s. Event: A collision in which the ego vehicle rear-ends a moving vehicle. At collision time, the ego vehicle overlaps with 100% of the width of the moving vehicle. | Travels with constant velocity: 8.33 m/s. Expected behavior: Forward collision warning (FCW) and triggering of Autonomous Emergency Braking (AEB) which stops the ego vehicle by applying brakes to avoid collision. |

## 13: scenario_13_AEB_CCRs_50overlap (Functional)
| Test Description | Target vehicles | Requirements on Vehicle Under Test |
| --- | --- | --- |
| scenario_13_AEB_CCRs_50overlap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 | Stationary Vehicle: Target vehicle is held stationary on the road. Event: A collision in which the ego vehicle overlaps with 50% of the width of the stationary vehicle. | Travels with constant velocity: 8.33 m/s. Expected behavior: Forward collision warning (FCW) and triggering of Autonomous Emergency Braking (AEB) which stops the ego vehicle by applying brakes to avoid collision. |

## 14: scenario_14_AEB_CCRs_-50overlap (Functional)
| Test Description | Target vehicles | Requirements on Vehicle Under Test |
| --- | --- | --- |
| scenario_14_AEB_CCRs_-50overlap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 | Stationary Vehicle: Target vehicle is held stationary on the road. Event: A collision in which the ego vehicle overlaps with -50% of the width of the stationary vehicle. When the ego vehicle is to the left of the other vehicle, the percent overlap is negative. | Travels with constant velocity: 8.33 m/s. Expected behavior: Forward collision warning (FCW) and triggering of Autonomous Emergency Braking (AEB) which stops the ego vehicle by applying brakes to avoid collision. |

## 15: scenario_15_AEB_CCRs_75overlap (Functional)
| Test Description | Target vehicles | Requirements on Vehicle Under Test |
| --- | --- | --- |
| scenario_15_AEB_CCRs_75overlap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 | Stationary Vehicle: Target vehicle is held stationary on the road. Event: A collision in which the ego vehicle overlaps with 75% of the width of the stationary vehicle. | Travels with constant velocity: 8.33 m/s. Expected behavior: Forward collision warning (FCW) and triggering of Autonomous Emergency Braking (AEB) which stops the ego vehicle by applying brakes to avoid collision. |

## 16: scenario_16_AEB_CCRs_-75overlap (Functional)
| Test Description | Target vehicles | Requirements on Vehicle Under Test |
| --- | --- | --- |
| scenario_16_AEB_CCRs_-75overlap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 | Stationary Vehicle: Target vehicle is held stationary on the road. Event: A collision in which the ego vehicle overlaps with -75% of the width of the stationary vehicle. When the ego vehicle is to the left of the other vehicle, the percent overlap is negative. | Travels with constant velocity: 8.33 m/s. Expected behavior: Forward collision warning (FCW) and triggering of Autonomous Emergency Braking (AEB) which stops the ego vehicle by applying brakes to avoid collision. |

## 17: scenario_17_AEB_CCRs_100overlap (Functional)
| Test Description | Target vehicles | Requirements on Vehicle Under Test |
| --- | --- | --- |
| scenario_17_AEB_CCRs_100overlap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 | Stationary Vehicle: Target vehicle is held stationary on the road. Event: A collision in which the ego vehicle overlaps with 100% of the width of the stationary vehicle. | Travels with constant velocity: 8.33 m/s. Expected behavior: Forward collision warning (FCW) and triggering of Autonomous Emergency Braking (AEB) which stops the ego vehicle by applying brakes to avoid collision. |

## 18: scenario_18_AEB_Pedestrian_Farside_50width (Functional)
| Test Description | Target Actor | Requirements on Vehicle Under Test |
| --- | --- | --- |
| scenario_18_AEB_Pedestrian_Farside_50width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 | Adult pedestrian: A pedestrian crosses the road from the left side (far side) at a constant speed of 2.2 m/s. Event: A collision in which the pedestrian is 50% of the way across the width of the ego vehicle. | Travels with constant velocity: 5.55 m/s. Expected behavior: Forward collision warning (FCW) and triggering of Autonomous Emergency Braking (AEB) which stops the ego vehicle by applying brakes to avoid collision. |

## 19: scenario_19_AEB_Pedestrian_Longitudinal_25width (Functional)
| Test Description | Target Actor | Requirements on Vehicle Under Test |
| --- | --- | --- |
| scenario_19_AEB_Pedestrian_Longitudinal_25width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 | Adult pedestrian: A pedestrian travelling on the road at a constant speed of 1.39 m/s. Event: A collision in which the pedestrian is 25% of the way across the width of the ego vehicle. | Travels with constant velocity: 13.9 m/s. Expected behavior: Forward collision warning (FCW) and triggering of Autonomous Emergency Braking (AEB) which stops the ego vehicle by applying brakes to avoid collision. |

## 20: scenario_20_AEB_Pedestrian_Longitudinal_50width (Functional)
| Test Description | Target Actor | Requirements on Vehicle Under Test |
| --- | --- | --- |
| scenario_20_AEB_Pedestrian_Longitudinal_50width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 | Adult pedestrian: A pedestrian travelling on the road at a constant speed of 1.39 m/s. Event: A collision in which the pedestrian is 50% of the way across the width of the ego vehicle. | Travels with constant velocity: 5.56 m/s. Expected behavior: Forward collision warning (FCW) and triggering of Autonomous Emergency Braking (AEB) which stops the ego vehicle by applying brakes to avoid collision. |

## 21: scenario_21_AEB_Pedestrian_Nearside_25width (Functional)
| Test Description | Target Actor | Requirements on Vehicle Under Test |
| --- | --- | --- |
| scenario_21_AEB_Pedestrian_Nearside_25width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 | Adult pedestrian: A pedestrian crosses the road from the right side (near side) at a constant speed of 1.39 m/s. Event: A collision in which the pedestrian is 25% of the way across the width of the ego vehicle. | Travels with constant velocity: 5.55 m/s. Expected behavior: Forward collision warning (FCW) and triggering of Autonomous Emergency Braking (AEB) which stops the ego vehicle by applying brakes to avoid collision. |

## 22: scenario_22_AEB_Pedestrian_Nearside_75width (Functional)
| Test Description | Target Actor | Requirements on Vehicle Under Test |
| --- | --- | --- |
| scenario_22_AEB_Pedestrian_Nearside_75width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 | Adult pedestrian: A pedestrian crosses the road from the right side (near side) at a constant speed of 1.39 m/s. Event: A collision in which the pedestrian is 75% of the way across the width of the ego vehicle. | Travels with constant velocity: 5.55 m/s. Expected behavior: Forward collision warning (FCW) and triggering of Autonomous Emergency Braking (AEB) which stops the ego vehicle by applying brakes to avoid collision. |

## 23: scenario_23_AEB_PedestrianChild_Nearside_50width (Functional)
| Test Description | Target Actor | Requirements on Vehicle Under Test |
| --- | --- | --- |
| scenario_23_AEB_PedestrianChild_Nearside_50width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 | Child pedestrian: A pedestrian crosses the road from the right side (near side) at a constant speed of 1.39 m/s. Obstructing Vehicles: The two vehicles are stationary on the road that obstructs the visibility of pedestrian for the VUT. Event: A collision in which the pedestrian is 50% of the way across the width of the ego vehicle. | Travels with constant velocity: 5.55 m/s. Expected behavior: Forward collision warning (FCW) and triggering of Autonomous Emergency Braking (AEB) which stops the ego vehicle by applying brakes to avoid collision. |

## 24: scenario_24_AEB_PedestrianTurning_Farside_10kph (Functional)
| Test Description | Target Actor | Requirements on Vehicle Under Test |
| --- | --- | --- |
| scenario_24_AEB_PedestrianTurning_Farside_10kph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 | Pedestrian: A pedestrian crosses the road from the far side with a constant speed of 1.3889 m/s when the ego vehicle takes a left turn at the intersection. Event: A collision in which the pedestrian is 50% of the way across the width of the ego vehicle. | Travels with constant velocity: 2.7778 m/s. Expected behavior: Forward collision warning (FCW) and triggering of Autonomous Emergency Braking (AEB) which stops the ego vehicle by applying brakes to avoid collision. |

## 25: scenario_25_AEB_PedestrianTurning_Nearside_10kph (Functional)
| Test Description | Target Actor | Requirements on Vehicle Under Test |
| --- | --- | --- |
| scenario_25_AEB_PedestrianTurning_Nearside_10kph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 | Pedestrian: A pedestrian crosses the road from the near side with a constant speed of 1.3889 m/s when the ego vehicle takes a right turn at the intersection. Event: A collision in which the pedestrian is 50% of the way across the width of the ego vehicle. | Travels with constant velocity: 2.7778 m/s. Expected behavior: Forward collision warning (FCW) and triggering of Autonomous Emergency Braking (AEB) which stops the ego vehicle by applying brakes to avoid collision. |

## 26: scenario_26_AEB_CCFtap_VUT_10kph_GVT_30kph (Functional)
| Test Description | Target Actor | Requirements on Vehicle Under Test |
| --- | --- | --- |
| scenario_26_AEB_CCFtap_VUT_10kph_GVT_30kph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 | Global Vehicle Target (GVT): The GVT follows a straight-line path in the lane adjacent to the vehicle under test (VUT)’s initial position, in the opposite direction to the VUT with a constant velocity of 8.33 m/s Event: A collision in which the front edges of the GVT meet with a lateral position that gives a 50% overlap of the width of the VUT. | Travels with constant velocity: 2.7778 m/s. Expected behavior: Forward collision warning (FCW) and triggering of Autonomous Emergency Braking (AEB) which stops the ego vehicle by applying brakes to avoid/mitigate impact of collision. |
